/*
Copyright (c) 2024 Cisco and/or its affiliates.

This software is licensed to you under the terms of the Cisco Sample
Code License, Version 1.1 (the "License"). You may obtain a copy of the
License at

               https://developer.cisco.com/docs/licenses

All use of the material herein must be in accordance with the terms of
the License. All rights not expressly granted by the License are
reserved. Unless required by applicable law or agreed to separately in
writing, software distributed under the License is distributed on an "AS
IS" BASIS, WITHOUT WARRANTIES OR CONDITIONS OF ANY KIND, either express
or implied.
*/

module site-service {
  namespace "https://its-best.ch/site";
  prefix "site-svc";

  description
   "This module is used in BRKOPS-2357 to validate input data
   for the site-service definition.";

  revision 2024-01-18 {
    description
     "Initial revision.";
  }
    
  typedef site-type {
    type enumeration {
      enum "DC";
      enum "Branch";
    }
  }

  list sites {
    key id;
    leaf id {
      type uint16 {
        range "1..254";
      }
    }

    leaf name {
      type string {
        pattern "site-.*";
      }
      mandatory true;
    }

    leaf type {
      type site-type;
      mandatory true;
    }

    leaf-list router {
      type string {
        pattern "C8K-.*";
      }
      min-elements 1;
    }

    leaf-list switches {
      type string {
        pattern "BRK2357S.*";
      }
      min-elements 0;
    }
  }
}
