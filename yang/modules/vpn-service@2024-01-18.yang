/*
Copyright (c) 2024 Cisco and/or its affiliates.

This software is licensed to you under the terms of the Cisco Sample
Code License, Version 1.1 (the "License"). You may obtain a copy of the
License at

               https://developer.cisco.com/docs/licenses

All use of the material herein must be in accordance with the terms of
the License. All rights not expressly granted by the License are
reserved. Unless required by applicable law or agreed to separately in
writing, software distributed under the License is distributed on an "AS
IS" BASIS, WITHOUT WARRANTIES OR CONDITIONS OF ANY KIND, either express
or implied.
*/

module vpn-service {
  namespace "https://its-best.ch/vpn";
  prefix "vpn-svc";
  
  import site-service {
    prefix "site-svc";
  }

  description
   "This module is used in BRKOPS-2357 to validate input data
   for the vpn-service definition.";

  revision 2024-01-18 {
    description
     "Initial revision.";
  }

  list vpns {
    key id;
    
    leaf id {
      type uint16 {
        range "100..110";
      }
    }

    leaf name {
      type string;
      mandatory true;
    }
    
    leaf-list sites {
      type leafref {
        path "/site-svc:sites/site-svc:type";
      }
      min-elements 1;
    }
  }
}
