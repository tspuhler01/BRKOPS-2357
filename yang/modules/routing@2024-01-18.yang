/*
Copyright (c) 2024 Cisco and/or its affiliates.

This software is licensed to you under the terms of the Cisco Sample
Code License, Version 1.1 (the "License"). You may obtain a copy of the
License at

               https://developer.cisco.com/docs/licenses

All use of the material herein must be in accordance with the terms of
the License. All rights not expressly granted by the License are
reserved. Unless required by applicable law or agreed to separately in
writing, software distributed under the License is distributed on an "AS
IS" BASIS, WITHOUT WARRANTIES OR CONDITIONS OF ANY KIND, either express
or implied.
*/

module routing {
  namespace "https://its-best.ch/routing";
  prefix "rtr";

  import site-service {
    prefix "site-svc";
  }

  import vpn-service {
    prefix "vpn-svc";
  }

  import ietf-inet-types {
    prefix "inet";
  }

  description
   "This module is used in BRKOPS-2357 to validate
   the routing variables.";

  revision 2024-01-18 {
    description
     "Initial revision.";
  }

  typedef phys-if {
    type string {
      pattern "GigabitEthernet1";
    }
  }

  typedef infra-if {
    type string {
      pattern "GigabitEthernet2.*";
    }
  }

  typedef sub-if {
    type string {
      pattern "GigabitEthernet2..*";
    }
  }
    
  list router {
    key "id";
    leaf id {
      type leafref {
        path "/site-svc:sites/site-svc:router";
      }
    }
    leaf type {
      type leafref {
        path "/site-svc:sites/site-svc:type";
      }
      mandatory true;
    }
    container variables {
      leaf system_site_id {
        type leafref {
          path "/site-svc:sites/site-svc:id";
        }
        mandatory true;
      }

      leaf system_system_ip {
        type inet:ipv4-address;
        mandatory true;
      }

      leaf system_host_name {
        type string {
          pattern "site-[0-9]{1,3}-r[0-9]{2}";
        }
        mandatory true;
      }

      leaf vpn0_interface {
        type phys-if;
        mandatory true;
      }

      leaf vpn0_ipv4_address {
        type inet:ipv4-prefix;
        mandatory true;
      }

      leaf vpn99_interface {
        type infra-if;
        mandatory true;
      }

      leaf vpn99_ipv4_address {
        type inet:ipv4-prefix;
        mandatory true;
      }

      leaf vpn100_interface {
        type sub-if;
      }

      leaf vpn100_ipv4_address {
        type inet:ipv4-prefix;
      }

      leaf vpn101_interface {
        type sub-if;
      }

      leaf vpn101_ipv4_address {
        type inet:ipv4-prefix;
      }

      leaf vpn102_interface {
        type sub-if;
      }

      leaf vpn102_ipv4_address {
        type inet:ipv4-prefix;
      }

      leaf vpn103_interface {
        type sub-if;
      }

      leaf vpn103_ipv4_address {
        type inet:ipv4-prefix;
      }

      leaf vpn104_interface {
        type sub-if;
      }

      leaf vpn104_ipv4_address {
        type inet:ipv4-prefix;
      }

      leaf vpn105_interface {
        type sub-if;
      }

      leaf vpn105_ipv4_address {
        type inet:ipv4-prefix;
      }

      leaf vpn106_interface {
        type sub-if;
      }

      leaf vpn106_ipv4_address {
        type inet:ipv4-prefix;
      }

      leaf vpn107_interface {
        type sub-if;
      }

      leaf vpn107_ipv4_address {
        type inet:ipv4-prefix;
      }

      leaf vpn108_interface {
        type sub-if;
      }

      leaf vpn108_ipv4_address {
        type inet:ipv4-prefix;
      }

      leaf vpn109_interface {
        type sub-if;
      }

      leaf vpn109_ipv4_address {
        type inet:ipv4-prefix;
      }

      leaf vpn110_interface {
        type sub-if;
      }

      leaf vpn110_ipv4_address {
        type inet:ipv4-prefix;
      }
    }
  }
  list vpns {
    key id;
    
    leaf id {
      type leafref {
        path "/vpn-svc:vpns/vpn-svc:id";
      }
    }

    leaf name {
      type leafref {
        path "/vpn-svc:vpns/vpn-svc:name";
      }
      mandatory true;
    }
    
    leaf-list sites {
      type leafref {
        path "/vpn-svc:vpns/vpn-svc:sites";
      }
      min-elements 1;
    }
  }
  leaf-list device_roles {
    type leafref {
        path "/vpn-svc:vpns/vpn-svc:sites";
      }
      min-elements 1;
  }
}
