/*
Copyright (c) 2024 Cisco and/or its affiliates.

This software is licensed to you under the terms of the Cisco Sample
Code License, Version 1.1 (the "License"). You may obtain a copy of the
License at

               https://developer.cisco.com/docs/licenses

All use of the material herein must be in accordance with the terms of
the License. All rights not expressly granted by the License are
reserved. Unless required by applicable law or agreed to separately in
writing, software distributed under the License is distributed on an "AS
IS" BASIS, WITHOUT WARRANTIES OR CONDITIONS OF ANY KIND, either express
or implied.
*/

module switching {
  namespace "https://its-best.ch/switching";
  prefix "sw";

  import site-service {
    prefix "site-svc";
  }

  import vpn-service {
    prefix "vpn-svc";
  }

  description
   "This module is used in BRKOPS-2357 to validate
   the switching variables.";

  revision 2024-01-18 {
    description
     "Initial revision.";
  }
    
  list switches {
    key "id";
    leaf id {
      type leafref {
        path "/site-svc:sites/site-svc:switches";
      }
    }

    leaf name {
      type string {
        pattern "site-[0-9]{1,3}-sw[0-9]{2}";
      }
      mandatory true;
    }
      
    leaf site {
      type leafref {
        path "/site-svc:sites/site-svc:name";
      }
      mandatory true;
    }

    leaf type {
      type leafref {
        path "/site-svc:sites/site-svc:type";
      }
      mandatory true;
    }
  }

  list vlans {
    key id;
    
    leaf id {
      type leafref {
        path "/vpn-svc:vpns/vpn-svc:id";
      }
    }

    leaf name {
      type leafref {
        path "/vpn-svc:vpns/vpn-svc:name";
      }
      mandatory true;
    }
    
    leaf-list sites {
      type leafref {
        path "../../switches/type";
      }
      min-elements 1;
    }
    list interfaces {
      key name;
      
      leaf type {
        type enumeration {
          enum "GigabitEthernet";
          enum "TenGigabitEthernet";
        }
        mandatory true;
      }
      
      leaf name {
        type string {
          pattern "1/0/[2-8]";
        }
      }
    }
  }
  
  leaf-list device_roles {
    type leafref {
        path "../switches/type";
      }
      min-elements 1;
  }
}
